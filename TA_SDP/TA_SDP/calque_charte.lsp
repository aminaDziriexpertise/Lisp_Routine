(defun c:cheeck_layers()

    (if (=  (tblsearch "layer" "GEX_BAT_allege") nil)(command "-layer" "n" "GEX_BAT_allege" "CO" "U" "0,0,255" "GEX_BAT_allege" "TL" "continuous" "GEX_BAT_allege" "EP" "0.13" "GEX_BAT_allege" "S" "allège extérieure et intérieure de fenêtre" "GEX_BAT_allege" ""))
    (if (=  (tblsearch "layer" "GEX_BAT_ascenseur") nil)(command "-layer" "n" "GEX_BAT_ascenseur" "CO" "U" "255,0,255" "GEX_BAT_ascenseur" "TL" "continuous" "GEX_BAT_ascenseur" "EP" "0.13" "GEX_BAT_ascenseur" "S" "ascenseur et monte-charge" "GEX_BAT_ascenseur" ""))
    (if (=  (tblsearch "layer" "GEX_BAT_axe") nil)(command "-layer" "n" "GEX_BAT_axe" "CO" "U" "255,0,0" "GEX_BAT_axe" "TL" "axes2" "GEX_BAT_axe" "EP" "0.3" "GEX_BAT_axe" "S" "axe chantier ou structure" "GEX_BAT_axe" ""))
    (if (=  (tblsearch "layer" "GEX_BAT_balcon_terrasse") nil)(command "-layer" "n" "GEX_BAT_balcon_terrasse" "CO" "U" "255,255,255" "GEX_BAT_balcon_terrasse" "TL" "continuous" "GEX_BAT_balcon_terrasse" "EP" "0.25" "GEX_BAT_balcon_terrasse" "S" "balcon et terrasse" "GEX_BAT_balcon_terrasse" ""))
    (if (=  (tblsearch "layer" "GEX_BAT_calage") nil)(command "-layer" "n" "GEX_BAT_calage" "CO" "U" "70,255,0" "GEX_BAT_calage" "TL" "continuous" "GEX_BAT_calage" "EP" "0.13" "GEX_BAT_calage" "S" "référence de calage des plans entre eux" "GEX_BAT_calage" ""))
    (if (=  (tblsearch "layer" "GEX_BAT_cheminee") nil)(command "-layer" "n" "GEX_BAT_cheminee" "CO" "U" "255,0,255" "GEX_BAT_cheminee" "TL" "continuous" "GEX_BAT_cheminee" "EP" "0.13" "GEX_BAT_cheminee" "S" "cheminée intérieure et exterieure" "GEX_BAT_cheminee" ""))
    (if (=  (tblsearch "layer" "GEX_BAT_cloison") nil)(command "-layer" "n" "GEX_BAT_cloison" "CO" "U" "255,255,0" "GEX_BAT_cloison" "TL" "continuous" "GEX_BAT_cloison" "EP" "0.18" "GEX_BAT_cloison" "S" "cloison non porteuse" "GEX_BAT_cloison" ""))
    (if (=  (tblsearch "layer" "GEX_BAT_cloison_vitre") nil)(command "-layer" "n" "GEX_BAT_cloison_vitre" "CO" "U" "0,255,0" "GEX_BAT_cloison_vitre" "TL" "continuous" "GEX_BAT_cloison_vitre" "EP" "0.13" "GEX_BAT_cloison_vitre" "S" "cloison non porteuse" "GEX_BAT_cloison_vitre" ""))
    (if (=  (tblsearch "layer" "GEX_BAT_coffrage") nil)(command "-layer" "n" "GEX_BAT_coffrage" "CO" "U" "0,0,255" "GEX_BAT_coffrage" "TL" "continuous" "GEX_BAT_coffrage" "EP" "0.13" "GEX_BAT_coffrage" "S" "cloison non porteuse" "GEX_BAT_coffrage" ""))
    (if (=  (tblsearch "layer" "GEX_BAT_escalier_rampe") nil)(command "-layer" "n" "GEX_BAT_escalier_rampe" "CO" "U" "0,255,255" "GEX_BAT_escalier_rampe" "TL" "continuous" "GEX_BAT_escalier_rampe" "EP" "0.15" "GEX_BAT_escalier_rampe" "S" "cloison non porteuse" "GEX_BAT_escalier_rampe" ""))
    (if (=  (tblsearch "layer" "GEX_BAT_fenetre") nil)(command "-layer" "n" "GEX_BAT_fenetre" "CO" "U" "0,255,0" "GEX_BAT_fenetre" "TL" "continuous" "GEX_BAT_fenetre" "EP" "0.13" "GEX_BAT_fenetre" "S" "cloison non porteuse" "GEX_BAT_fenetre" ""))
    (if (=  (tblsearch "layer" "GEX_BAT_fx_plafond") nil)(command "-layer" "n" "GEX_BAT_fx_plafond" "CO" "U" "0,127,255" "GEX_BAT_fx_plafond" "TL" "cache2" "GEX_BAT_fx_plafond" "EP" "0.15" "GEX_BAT_fx_plafond" "S" "cloison non porteuse" "GEX_BAT_fx_plafond" ""))
    (if (=  (tblsearch "layer" "GEX_BAT_gaine") nil)(command "-layer" "n" "GEX_BAT_gaine" "CO" "U" "255,255,255" "GEX_BAT_gaine" "TL" "continuous" "GEX_BAT_gaine" "EP" "0.25" "GEX_BAT_gaine" "S" "cloison non porteuse" "GEX_BAT_gaine" ""))
    (if (=  (tblsearch "layer" "GEX_BAT_ipn") nil)(command "-layer" "n" "GEX_BAT_ipn" "CO" "U" "255,255,255" "GEX_BAT_ipn" "TL" "continuous" "GEX_BAT_ipn" "EP" "0.25" "GEX_BAT_ipn" "S" "cloison non porteuse" "GEX_BAT_ipn" ""))
    (if (=  (tblsearch "layer" "GEX_BAT_linteau_cloison") nil)(command "-layer" "n" "GEX_BAT_linteau_cloison" "CO" "U" "0,255,0" "GEX_BAT_linteau_cloison" "TL" "cache2" "GEX_BAT_linteau_cloison" "EP" "0.13" "GEX_BAT_linteau_cloison" "S" "cloison non porteuse" "GEX_BAT_linteau_cloison" ""))
    (if (=  (tblsearch "layer" "GEX_BAT_linteau_mur") nil)(command "-layer" "n" "GEX_BAT_linteau_mur" "CO" "U" "255,0,255" "GEX_BAT_linteau_mur" "TL" "cache2" "GEX_BAT_linteau_mur" "EP" "0.13" "GEX_BAT_linteau_mur" "S" "cloison non porteuse" "GEX_BAT_linteau_mur" ""))
    (if (=  (tblsearch "layer" "GEX_BAT_lucarne") nil)(command "-layer" "n" "GEX_BAT_lucarne" "CO" "U" "0,255,0" "GEX_BAT_lucarne" "TL" "cache2" "GEX_BAT_lucarne" "EP" "0.13" "GEX_BAT_lucarne" "S" "cloison non porteuse" "GEX_BAT_lucarne" ""))
    (if (=  (tblsearch "layer" "GEX_BAT_marche") nil)(command "-layer" "n" "GEX_BAT_marche" "CO" "U" "127,223,255" "GEX_BAT_marche" "TL" "continuous" "GEX_BAT_marche" "EP" "0.15" "GEX_BAT_marche" "S" "cloison non porteuse" "GEX_BAT_marche" ""))
    (if (=  (tblsearch "layer" "GEX_BAT_mur") nil)(command "-layer" "n" "GEX_BAT_mur" "CO" "U" "255,0,0" "GEX_BAT_mur" "TL" "continuous" "GEX_BAT_mur" "EP" "0.30" "GEX_BAT_mur" "S" "cloison non porteuse" "GEX_BAT_mur" ""))
    (if (=  (tblsearch "layer" "GEX_BAT_mur_bas") nil)(command "-layer" "n" "GEX_BAT_mur_bas" "CO" "U" "0,191,255" "GEX_BAT_mur_bas" "TL" "continuous" "GEX_BAT_mur_bas" "EP" "0.15" "GEX_BAT_mur_bas" "S" "cloison non porteuse" "GEX_BAT_mur_bas" ""))
    (if (=  (tblsearch "layer" "GEX_BAT_plafond") nil)(command "-layer" "n" "GEX_BAT_plafond" "CO" "U" "104,106,109" "GEX_BAT_plafond" "TL" "cache2" "GEX_BAT_plafond" "EP" "0.15" "GEX_BAT_plafond" "S" "cloison non porteuse" "GEX_BAT_plafond" ""))
    (if (=  (tblsearch "layer" "GEX_BAT_poutre") nil)(command "-layer" "n" "GEX_BAT_poutre" "CO" "U" "255,0,255" "GEX_BAT_poutre" "TL" "cache2" "GEX_BAT_poutre" "EP" "0.13" "GEX_BAT_poutre" "S" "cloison non porteuse" "GEX_BAT_poutre" ""))
    (if (=  (tblsearch "layer" "GEX_BAT_tablette") nil)(command "-layer" "n" "GEX_BAT_tablette" "CO" "U" "255,0,255" "GEX_BAT_tablette" "TL" "continuous" "GEX_BAT_tablette" "EP" "0.13" "GEX_BAT_tablette" "S" "cloison non porteuse" "GEX_BAT_tablette" ""))
    (if (=  (tblsearch "layer" "GEX_BAT_toiture") nil)(command "-layer" "n" "GEX_BAT_toiture" "CO" "U" "127,223,255" "GEX_BAT_toiture" "TL" "continuous" "GEX_BAT_toiture" "EP" "0.15" "GEX_BAT_toiture" "S" "cloison non porteuse" "GEX_BAT_toiture" ""))
    (if (=  (tblsearch "layer" "GEX_BAT_trappe") nil)(command "-layer" "n" "GEX_BAT_trappe" "CO" "U" "255,0,255" "GEX_BAT_trappe" "TL" "cache2" "GEX_BAT_trappe" "EP" "0.13" "GEX_BAT_trappe" "S" "cloison non porteuse" "GEX_BAT_trappe" ""))
    (if (=  (tblsearch "layer" "GEX_BAT_tremie") nil)(command "-layer" "n" "GEX_BAT_tremie" "CO" "U" "145,148,148" "GEX_BAT_tremie" "TL" "continuous" "GEX_BAT_tremie" "EP" "0.15" "GEX_BAT_tremie" "S" "cloison non porteuse" "GEX_BAT_tremie" ""))
    (if (=  (tblsearch "layer" "GEX_BAT_vitrine") nil)(command "-layer" "n" "GEX_BAT_vitrine" "CO" "U" "0,255,0" "GEX_BAT_vitrine" "TL" "cachex2" "GEX_BAT_vitrine" "EP" "0.13" "GEX_BAT_vitrine" "S" "cloison non porteuse" "GEX_BAT_vitrine" ""))
    (if (=  (tblsearch "layer" "GEX_COT_cotation") nil)(command "-layer" "n" "GEX_COT_cotation" "CO" "U" "255,0,255" "GEX_COT_cotation" "TL" "continuous" "GEX_COT_cotation" "EP" "0.13" "GEX_COT_cotation" "S" "cloison non porteuse" "GEX_COT_cotation" ""))
    (if (=  (tblsearch "layer" "GEX_COT_hauteur") nil)(command "-layer" "n" "GEX_COT_hauteur" "CO" "U" "255,255,0" "GEX_COT_hauteur" "TL" "continuous" "GEX_COT_hauteur" "EP" "0.18" "GEX_COT_hauteur" "S" "cloison non porteuse" "GEX_COT_hauteur" ""))
    (if (=  (tblsearch "layer" "GEX_COT_Z") nil)(command "-layer" "n" "GEX_COT_Z" "CO" "U" "0,255,255" "GEX_COT_Z" "TL" "continuous" "GEX_COT_Z" "EP" "0.15" "GEX_COT_Z" "S" "cloison non porteuse" "GEX_COT_Z" ""))
    (if (=  (tblsearch "layer" "GEX_COT_Z_allege_linteau") nil)(command "-layer" "n" "GEX_COT_Z_allege_linteau" "CO" "U" "0,255,255" "GEX_COT_Z_allege_linteau" "TL" "continuous" "GEX_COT_Z_allege_linteau" "EP" "0.15" "GEX_COT_Z_allege_linteau" "S" "cloison non porteuse" "GEX_COT_Z_allege_linteau" ""))
    (if (=  (tblsearch "layer" "GEX_EDS_poly_div") nil)(command "-layer" "n" "GEX_EDS_poly_div" "CO" "U" "255,255,255" "GEX_EDS_poly_div" "TL" "continuous" "GEX_EDS_poly_div" "EP" "0.25" "GEX_EDS_poly_div" "S" "cloison non porteuse" "GEX_EDS_poly_div" ""))
    (if (=  (tblsearch "layer" "GEX_EDS_poly_surf_C") nil)(command "-layer" "n" "GEX_EDS_poly_surf_C" "CO" "U" "255,0,0" "GEX_EDS_poly_surf_C" "TL" "continuous" "GEX_EDS_poly_surf_C" "EP" "0.3" "GEX_EDS_poly_surf_C" "S" "cloison non porteuse" "GEX_EDS_poly_surf_C" ""))
    (if (=  (tblsearch "layer" "GEX_EDS_poly_surf_HC") nil)(command "-layer" "n" "GEX_EDS_poly_surf_HC" "CO" "U" "0,255,0" "GEX_EDS_poly_surf_HC" "TL" "continuous" "GEX_EDS_poly_surf_HC" "EP" "0.13" "GEX_EDS_poly_surf_HC" "S" "cloison non porteuse" "GEX_EDS_poly_surf_HC" ""))
    (if (=  (tblsearch "layer" "GEX_EDS_sdp_1-SDP") nil)(command "-layer" "n" "GEX_EDS_sdp_1-SDP" "CO" "U" "255,0,0" "GEX_EDS_sdp_1-SDP" "TL" "axes" "GEX_EDS_sdp_1-SDP" "EP" "0.30" "GEX_EDS_sdp_1-SDP" "S" "Calques initiés par le gabarit de présentation des SDP" "GEX_EDS_sdp_1-SDP" ""))
    (if (=  (tblsearch "layer" "GEX_EDS_sdp_2-tremie") nil)(command "-layer" "n" "GEX_EDS_sdp_2-tremie" "CO" "U" "255,255,127" "GEX_EDS_sdp_2-tremie" "TL" "continuous" "GEX_EDS_sdp_2-tremie" "EP" "0.18" "GEX_EDS_sdp_2-tremie" "S" "Calques initiés par le gabarit de présentation des SDP" "GEX_EDS_sdp_2-tremie" ""))
    (if (=  (tblsearch "layer" "GEX_EDS_sdp_3-h-180") nil)(command "-layer" "n" "GEX_EDS_sdp_3-h-180" "CO" "U" "204,102,102" "GEX_EDS_sdp_3-h-180" "TL" "continuous" "GEX_EDS_sdp_3-h-180" "EP" "0.18" "GEX_EDS_sdp_3-h-180" "S" "Calques initiés par le gabarit de présentation des SDP" "GEX_EDS_sdp_3-h-180" ""))
    (if (=  (tblsearch "layer" "GEX_EDS_sdp_5-PK") nil)(command "-layer" "n" "GEX_EDS_sdp_5-PK" "CO" "U" "113,116,118" "GEX_EDS_sdp_5-PK" "TL" "continuous" "GEX_EDS_sdp_5-PK" "EP" "0.15" "GEX_EDS_sdp_5-PK" "S" "Calques initiés par le gabarit de présentation des SDP" "GEX_EDS_sdp_5-PK" ""))
    (if (=  (tblsearch "layer" "GEX_EDS_sdp_6-combles") nil)(command "-layer" "n" "GEX_EDS_sdp_6-combles" "CO" "U" "102,0,204" "GEX_EDS_sdp_6-combles" "TL" "continuous" "GEX_EDS_sdp_6-combles" "EP" "" "GEX_EDS_sdp_6-combles" "S" "Calques initiés par le gabarit de présentation des SDP" "GEX_EDS_sdp_6-combles" ""))
    (if (=  (tblsearch "layer" "GEX_EDS_sdp_7-LT") nil)(command "-layer" "n" "GEX_EDS_sdp_7-LT" "CO" "U" "0,127,255" "GEX_EDS_sdp_7-LT" "TL" "continuous" "GEX_EDS_sdp_7-LT" "EP" "" "GEX_EDS_sdp_7-LT" "S" "Calques initiés par le gabarit de présentation des SDP" "GEX_EDS_sdp_7-LT" ""))
    (if (=  (tblsearch "layer" "GEX_EDS_sdp_8-cave") nil)(command "-layer" "n" "GEX_EDS_sdp_8-cave" "CO" "U" "255,255,0" "GEX_EDS_sdp_8-cave" "TL" "continuous" "GEX_EDS_sdp_8-cave" "EP" "" "GEX_EDS_sdp_8-cave" "S" "Calques initiés par le gabarit de présentation des SDP" "GEX_EDS_sdp_8-cave" ""))
    (if (=  (tblsearch "layer" "GEX_EDS_shob_contour") nil)(command "-layer" "n" "GEX_EDS_shob_contour" "CO" "U" "255,255,0" "GEX_EDS_shob_contour" "TL" "continuous" "GEX_EDS_shob_contour" "EP" "" "GEX_EDS_shob_contour" "S" "Calques initiés par le gabarit de présentation des SHO" "GEX_EDS_shob_contour" ""))
    (if (=  (tblsearch "layer" "GEX_EDS_shob_tremie") nil)(command "-layer" "n" "GEX_EDS_shob_tremie" "CO" "U" "255,255,127" "GEX_EDS_shob_tremie" "TL" "continuous" "GEX_EDS_shob_tremie" "EP" "" "GEX_EDS_shob_tremie" "S" "Calques initiés par le gabarit de présentation des SHO" "GEX_EDS_shob_tremie" ""))
    (if (=  (tblsearch "layer" "GEX_EDS_shon_cave") nil)(command "-layer" "n" "GEX_EDS_shon_cave" "CO" "U" "255,255,0" "GEX_EDS_shon_cave" "TL" "continuous" "GEX_EDS_shon_cave" "EP" "" "GEX_EDS_shon_cave" "S" "Calques initiés par le gabarit de présentation des SHO" "GEX_EDS_shon_cave" ""))
    (if (=  (tblsearch "layer" "GEX_EDS_shon_h-180") nil)(command "-layer" "n" "GEX_EDS_shon_h-180" "CO" "U" "204,102,102" "GEX_EDS_shon_h-180" "TL" "continuous" "GEX_EDS_shon_h-180" "EP" "" "GEX_EDS_shon_h-180" "S" "Calques initiés par le gabarit de présentation des SHO" "GEX_EDS_shon_h-180" ""))
    (if (=  (tblsearch "layer" "GEX_EDS_shon_LTG") nil)(command "-layer" "n" "GEX_EDS_shon_LTG" "CO" "U" "0,127,255" "GEX_EDS_shon_LTG" "TL" "continuous" "GEX_EDS_shon_LTG" "EP" "" "GEX_EDS_shon_LTG" "S" "Calques initiés par le gabarit de présentation des SHO" "GEX_EDS_shon_LTG" ""))
    (if (=  (tblsearch "layer" "GEX_EDS_shon_PK") nil)(command "-layer" "n" "GEX_EDS_shon_PK" "CO" "U" "113,116,118" "GEX_EDS_shon_PK" "TL" "continuous" "GEX_EDS_shon_PK" "EP" "" "GEX_EDS_shon_PK" "S" "Calques initiés par le gabarit de présentation des SHO" "GEX_EDS_shon_PK" ""))
    (if (=  (tblsearch "layer" "GEX_EDS_shon_SNC") nil)(command "-layer" "n" "GEX_EDS_shon_SNC" "CO" "U" "191,255,127" "GEX_EDS_shon_SNC" "TL" "continuous" "GEX_EDS_shon_SNC" "EP" "" "GEX_EDS_shon_SNC" "S" "Calques initiés par le gabarit de présentation des SHO" "GEX_EDS_shon_SNC" ""))
    (if (=  (tblsearch "layer" "GEX_EDS_SU_archives") nil)(command "-layer" "n" "GEX_EDS_SU_archives" "CO" "U" "255,255,255" "GEX_EDS_SU_archives" "TL" "continuous" "GEX_EDS_SU_archives" "EP" "0.25" "GEX_EDS_SU_archives" "S" "Calques initiés par le gabarit de présentation des SU" "GEX_EDS_SU_archives" ""))
    (if (=  (tblsearch "layer" "GEX_EDS_SU_bureau") nil)(command "-layer" "n" "GEX_EDS_SU_bureau" "CO" "U" "255,255,255" "GEX_EDS_SU_bureau" "TL" "continuous" "GEX_EDS_SU_bureau" "EP" "0.25" "GEX_EDS_SU_bureau" "S" "Calques initiés par le gabarit de présentation des SU" "GEX_EDS_SU_bureau" ""))
    (if (=  (tblsearch "layer" "GEX_EDS_SU_circ_gene") nil)(command "-layer" "n" "GEX_EDS_SU_circ_gene" "CO" "U" "255,255,255" "GEX_EDS_SU_circ_gene" "TL" "continuous" "GEX_EDS_SU_circ_gene" "EP" "0.25" "GEX_EDS_SU_circ_gene" "S" "Calques initiés par le gabarit de présentation des SU" "GEX_EDS_SU_circ_gene" ""))
    (if (=  (tblsearch "layer" "GEX_EDS_SU_circ_priv") nil)(command "-layer" "n" "GEX_EDS_SU_circ_priv" "CO" "U" "255,255,255" "GEX_EDS_SU_circ_priv" "TL" "continuous" "GEX_EDS_SU_circ_priv" "EP" "0.25" "GEX_EDS_SU_circ_priv" "S" "Calques initiés par le gabarit de présentation des SU" "GEX_EDS_SU_circ_priv" ""))
    (if (=  (tblsearch "layer" "GEX_EDS_SU_comm_reser") nil)(command "-layer" "n" "GEX_EDS_SU_comm_reser" "CO" "U" "255,255,255" "GEX_EDS_SU_comm_reser" "TL" "continuous" "GEX_EDS_SU_comm_reser" "EP" "0.25" "GEX_EDS_SU_comm_reser" "S" "Calques initiés par le gabarit de présentation des SU" "GEX_EDS_SU_comm_reser" ""))
    (if (=  (tblsearch "layer" "GEX_EDS_SU_commerce") nil)(command "-layer" "n" "GEX_EDS_SU_commerce" "CO" "U" "255,255,255" "GEX_EDS_SU_commerce" "TL" "continuous" "GEX_EDS_SU_commerce" "EP" "0.25" "GEX_EDS_SU_commerce" "S" "Calques initiés par le gabarit de présentation des SU" "GEX_EDS_SU_commerce" ""))
    (if (=  (tblsearch "layer" "GEX_EDS_SU_h-180") nil)(command "-layer" "n" "GEX_EDS_SU_h-180" "CO" "U" "255,255,255" "GEX_EDS_SU_h-180" "TL" "continuous" "GEX_EDS_SU_h-180" "EP" "0.25" "GEX_EDS_SU_h-180" "S" "Calques initiés par le gabarit de présentation des SU" "GEX_EDS_SU_h-180" ""))
    (if (=  (tblsearch "layer" "GEX_EDS_SU_habitation") nil)(command "-layer" "n" "GEX_EDS_SU_habitation" "CO" "U" "255,255,255" "GEX_EDS_SU_habitation" "TL" "continuous" "GEX_EDS_SU_habitation" "EP" "0.25" "GEX_EDS_SU_habitation" "S" "Calques initiés par le gabarit de présentation des SU" "GEX_EDS_SU_habitation" ""))
    (if (=  (tblsearch "layer" "GEX_EDS_SU_loc_dispo") nil)(command "-layer" "n" "GEX_EDS_SU_loc_dispo" "CO" "U" "255,255,255" "GEX_EDS_SU_loc_dispo" "TL" "continuous" "GEX_EDS_SU_loc_dispo" "EP" "0.25" "GEX_EDS_SU_loc_dispo" "S" "Calques initiés par le gabarit de présentation des SU" "GEX_EDS_SU_loc_dispo" ""))
    (if (=  (tblsearch "layer" "GEX_EDS_SU_loc_entretien") nil)(command "-layer" "n" "GEX_EDS_SU_loc_entretien" "CO" "U" "255,255,255" "GEX_EDS_SU_loc_entretien" "TL" "continuous" "GEX_EDS_SU_loc_entretien" "EP" "0.25" "GEX_EDS_SU_loc_entretien" "S" "Calques initiés par le gabarit de présentation des SU" "GEX_EDS_SU_loc_entretien" ""))
    (if (=  (tblsearch "layer" "GEX_EDS_SU_loc_social") nil)(command "-layer" "n" "GEX_EDS_SU_loc_social" "CO" "U" "255,255,255" "GEX_EDS_SU_loc_social" "TL" "continuous" "GEX_EDS_SU_loc_social" "EP" "0.25" "GEX_EDS_SU_loc_social" "S" "Calques initiés par le gabarit de présentation des SU" "GEX_EDS_SU_loc_social" ""))
    (if (=  (tblsearch "layer" "GEX_EDS_SU_LTG") nil)(command "-layer" "n" "GEX_EDS_SU_LTG" "CO" "U" "255,255,255" "GEX_EDS_SU_LTG" "TL" "continuous" "GEX_EDS_SU_LTG" "EP" "0.25" "GEX_EDS_SU_LTG" "S" "Calques initiés par le gabarit de présentation des SU" "GEX_EDS_SU_LTG" ""))
    (if (=  (tblsearch "layer" "GEX_EDS_SU_LTP") nil)(command "-layer" "n" "GEX_EDS_SU_LTP" "CO" "U" "255,255,255" "GEX_EDS_SU_LTP" "TL" "continuous" "GEX_EDS_SU_LTP" "EP" "0.25" "GEX_EDS_SU_LTP" "S" "Calques initiés par le gabarit de présentation des SU" "GEX_EDS_SU_LTP" ""))
    (if (=  (tblsearch "layer" "GEX_EDS_SU_palier") nil)(command "-layer" "n" "GEX_EDS_SU_palier" "CO" "U" "255,255,255" "GEX_EDS_SU_palier" "TL" "continuous" "GEX_EDS_SU_palier" "EP" "0.25" "GEX_EDS_SU_palier" "S" "Calques initiés par le gabarit de présentation des SU" "GEX_EDS_SU_palier" ""))
    (if (=  (tblsearch "layer" "GEX_EDS_SU_palier_ext") nil)(command "-layer" "n" "GEX_EDS_SU_palier_ext" "CO" "U" "255,255,255" "GEX_EDS_SU_palier_ext" "TL" "continuous" "GEX_EDS_SU_palier_ext" "EP" "0.25" "GEX_EDS_SU_palier_ext" "S" "Calques initiés par le gabarit de présentation des SU" "GEX_EDS_SU_palier_ext" ""))
    (if (=  (tblsearch "layer" "GEX_EDS_SU_parking") nil)(command "-layer" "n" "GEX_EDS_SU_parking" "CO" "U" "255,255,255" "GEX_EDS_SU_parking" "TL" "continuous" "GEX_EDS_SU_parking" "EP" "0.25" "GEX_EDS_SU_parking" "S" "Calques initiés par le gabarit de présentation des SU" "GEX_EDS_SU_parking" ""))
    (if (=  (tblsearch "layer" "GEX_EDS_SU_rie") nil)(command "-layer" "n" "GEX_EDS_SU_rie" "CO" "U" "255,255,255" "GEX_EDS_SU_rie" "TL" "continuous" "GEX_EDS_SU_rie" "EP" "0.25" "GEX_EDS_SU_rie" "S" "Calques initiés par le gabarit de présentation des SU" "GEX_EDS_SU_rie" ""))
    (if (=  (tblsearch "layer" "GEX_EDS_SU_rie_annexe") nil)(command "-layer" "n" "GEX_EDS_SU_rie_annexe" "CO" "U" "255,255,255" "GEX_EDS_SU_rie_annexe" "TL" "continuous" "GEX_EDS_SU_rie_annexe" "EP" "0.25" "GEX_EDS_SU_rie_annexe" "S" "Calques initiés par le gabarit de présentation des SU" "GEX_EDS_SU_rie_annexe" ""))
    (if (=  (tblsearch "layer" "GEX_EDS_SU_sanitaires") nil)(command "-layer" "n" "GEX_EDS_SU_sanitaires" "CO" "U" "255,255,255" "GEX_EDS_SU_sanitaires" "TL" "continuous" "GEX_EDS_SU_sanitaires" "EP" "0.25" "GEX_EDS_SU_sanitaires" "S" "Calques initiés par le gabarit de présentation des SU" "GEX_EDS_SU_sanitaires" ""))
    (if (=  (tblsearch "layer" "GEX_EDS_SU_tablette") nil)(command "-layer" "n" "GEX_EDS_SU_tablette" "CO" "U" "255,255,255" "GEX_EDS_SU_tablette" "TL" "continuous" "GEX_EDS_SU_tablette" "EP" "0.25" "GEX_EDS_SU_tablette" "S" "Calques initiés par le gabarit de présentation des SU" "GEX_EDS_SU_tablette" ""))
    (if (=  (tblsearch "layer" "GEX_EDS_SU_terrasse") nil)(command "-layer" "n" "GEX_EDS_SU_terrasse" "CO" "U" "255,255,255" "GEX_EDS_SU_terrasse" "TL" "continuous" "GEX_EDS_SU_terrasse" "EP" "0.25" "GEX_EDS_SU_terrasse" "S" "Calques initiés par le gabarit de présentation des SU" "GEX_EDS_SU_terrasse" ""))
    (if (=  (tblsearch "layer" "GEX_EXT_bordure_trottoir") nil)(command "-layer" "n" "GEX_EXT_bordure_trottoir" "CO" "U" "0,255,255" "GEX_EXT_bordure_trottoir" "TL" "continuous" "GEX_EXT_bordure_trottoir" "EP" "0.15" "GEX_EXT_bordure_trottoir" "S" "cloison non porteuse" "GEX_EXT_bordure_trottoir" ""))
    (if (=  (tblsearch "layer" "GEX_EXT_cloture") nil)(command "-layer" "n" "GEX_EXT_cloture" "CO" "U" "255,255,255" "GEX_EXT_cloture" "TL" "limite1" "GEX_EXT_cloture" "EP" "0.25" "GEX_EXT_cloture" "S" "" "GEX_EXT_cloture" ""))
    (if (=  (tblsearch "layer" "GEX_EXT_ferronnerie") nil)(command "-layer" "n" "GEX_EXT_ferronnerie" "CO" "U" "255,0,255" "GEX_EXT_ferronnerie" "TL" "continuous" "GEX_EXT_ferronnerie" "EP" "0.13" "GEX_EXT_ferronnerie" "S" "" "GEX_EXT_ferronnerie" ""))
    (if (=  (tblsearch "layer" "GEX_EXT_grille") nil)(command "-layer" "n" "GEX_EXT_grille" "CO" "U" "255,0,255" "GEX_EXT_grille" "TL" "cache2" "GEX_EXT_grille" "EP" "0.13" "GEX_EXT_grille" "S" "" "GEX_EXT_grille" ""))
    (if (=  (tblsearch "layer" "GEX_EXT_mobilier_urbain") nil)(command "-layer" "n" "GEX_EXT_mobilier_urbain" "CO" "U" "0,255,0" "GEX_EXT_mobilier_urbain" "TL" "continuous" "GEX_EXT_mobilier_urbain" "EP" "0.13" "GEX_EXT_mobilier_urbain" "S" "" "GEX_EXT_mobilier_urbain" ""))
    (if (=  (tblsearch "layer" "GEX_EXT_talus") nil)(command "-layer" "n" "GEX_EXT_talus" "CO" "U" "0,153,38" "GEX_EXT_talus" "TL" "continuous" "GEX_EXT_talus" "EP" "" "GEX_EXT_talus" "S" "" "GEX_EXT_talus" ""))
    (if (=  (tblsearch "layer" "GEX_EXT_vegetation") nil)(command "-layer" "n" "GEX_EXT_vegetation" "CO" "U" "0,255,0" "GEX_EXT_vegetation" "TL" "continuous" "GEX_EXT_vegetation" "EP" "0.18" "GEX_EXT_vegetation" "S" "y compris les hachures de végétation" "GEX_EXT_vegetation" ""))
    (if (=  (tblsearch "layer" "GEX_EXT_voirie") nil)(command "-layer" "n" "GEX_EXT_voirie" "CO" "U" "255,255,0" "GEX_EXT_voirie" "TL" "continuous" "GEX_EXT_voirie" "EP" "0.18" "GEX_EXT_voirie" "S" "" "GEX_EXT_voirie" ""))
    (if (=  (tblsearch "layer" "GEX_FON_cadastre") nil)(command "-layer" "n" "GEX_FON_cadastre" "CO" "U" "255,0,0" "GEX_FON_cadastre" "TL" "axes2" "GEX_FON_cadastre" "EP" "0.30" "GEX_FON_cadastre" "S" "" "GEX_FON_cadastre" ""))
    (if (=  (tblsearch "layer" "GEX_FON_heb_mitoyen") nil)(command "-layer" "n" "GEX_FON_heb_mitoyen" "CO" "U" "255,255,0" "GEX_FON_heb_mitoyen" "TL" "axes" "GEX_FON_heb_mitoyen" "EP" "0.18" "GEX_FON_heb_mitoyen" "S" "" "GEX_FON_heb_mitoyen" ""))
    (if (=  (tblsearch "layer" "GEX_FON_heb_proprio") nil)(command "-layer" "n" "GEX_FON_heb_proprio" "CO" "U" "0,255,255" "GEX_FON_heb_proprio" "TL" "cache2" "GEX_FON_heb_proprio" "EP" "0.15" "GEX_FON_heb_proprio" "S" "" "GEX_FON_heb_proprio" ""))
    (if (=  (tblsearch "layer" "GEX_FON_heb_voisin") nil)(command "-layer" "n" "GEX_FON_heb_voisin" "CO" "U" "255,0,0" "GEX_FON_heb_voisin" "TL" "continuous" "GEX_FON_heb_voisin" "EP" "0.30" "GEX_FON_heb_voisin" "S" "" "GEX_FON_heb_voisin" ""))
    (if (=  (tblsearch "layer" "GEX_FON_limite_prop") nil)(command "-layer" "n" "GEX_FON_limite_prop" "CO" "U" "255,191,0" "GEX_FON_limite_prop" "TL" "continuous" "GEX_FON_limite_prop" "EP" "0.18" "GEX_FON_limite_prop" "S" "" "GEX_FON_limite_prop" ""))
    (if (=  (tblsearch "layer" "GEX_FON_mitoyen") nil)(command "-layer" "n" "GEX_FON_mitoyen" "CO" "U" "255,255,0" "GEX_FON_mitoyen" "TL" "axes" "GEX_FON_mitoyen" "EP" "0.18" "GEX_FON_mitoyen" "S" "" "GEX_FON_mitoyen" ""))
    (if (=  (tblsearch "layer" "GEX_FON_servitude") nil)(command "-layer" "n" "GEX_FON_servitude" "CO" "U" "255,191,0" "GEX_FON_servitude" "TL" "continuous" "GEX_FON_servitude" "EP" "0.18" "GEX_FON_servitude" "S" "" "GEX_FON_servitude" ""))
    (if (=  (tblsearch "layer" "GEX_FON_perimetre_ASL") nil)(command "-layer" "n" "GEX_FON_perimetre_ASL" "CO" "U" "255,191,0" "GEX_FON_perimetre_ASL" "TL" "continuous" "GEX_FON_perimetre_ASL" "EP" "0.18" "GEX_FON_perimetre_ASL" "S" "" "GEX_FON_perimetre_ASL" ""))
    (if (=  (tblsearch "layer" "GEX_HAB_designation") nil)(command "-layer" "n" "GEX_HAB_designation" "CO" "U" "255,255,255" "GEX_HAB_designation" "TL" "continuous" "GEX_HAB_designation" "EP" "0.18" "GEX_HAB_designation" "S" "" "GEX_HAB_designation" ""))
    (if (=  (tblsearch "layer" "GEX_HAB_fleche_entree") nil)(command "-layer" "n" "GEX_HAB_fleche_entree" "CO" "U" "255,255,0" "GEX_HAB_fleche_entree" "TL" "continuous" "GEX_HAB_fleche_entree" "EP" "0.18" "GEX_HAB_fleche_entree" "S" "" "GEX_HAB_fleche_entree" ""))
    (if (=  (tblsearch "layer" "GEX_HAB_h-180") nil)(command "-layer" "n" "GEX_HAB_h-180" "CO" "U" "255,255,255" "GEX_HAB_h-180" "TL" "tiretpt" "GEX_HAB_h-180" "EP" "0.18" "GEX_HAB_h-180" "S" "" "GEX_HAB_h-180" ""))
    (if (=  (tblsearch "layer" "GEX_HAB_hachure") nil)(command "-layer" "n" "GEX_HAB_hachure" "CO" "U" "255,255,0" "GEX_HAB_hachure" "TL" "continuous" "GEX_HAB_hachure" "EP" "0.18" "GEX_HAB_hachure" "S" "" "GEX_HAB_hachure" ""))
    (if (=  (tblsearch "layer" "GEX_HAB_limite_lot") nil)(command "-layer" "n" "GEX_HAB_limite_lot" "CO" "U" "255,255,0" "GEX_HAB_limite_lot" "TL" "continuous" "GEX_HAB_limite_lot" "EP" "0.18" "GEX_HAB_limite_lot" "S" "" "GEX_HAB_limite_lot" ""))
    (if (=  (tblsearch "layer" "GEX_HAB_mur_poch") nil)(command "-layer" "n" "GEX_HAB_mur_poch" "CO" "U" "255,255,0" "GEX_HAB_mur_poch" "TL" "continuous" "GEX_HAB_mur_poch" "EP" "0.18" "GEX_HAB_mur_poch" "S" "possibilité de forcer la couleur" "GEX_HAB_mur_poch" ""))
    (if (=  (tblsearch "layer" "GEX_HAB_no_lot") nil)(command "-layer" "n" "GEX_HAB_no_lot" "CO" "U" "255,255,0" "GEX_HAB_no_lot" "TL" "continuous" "GEX_HAB_no_lot" "EP" "0.18" "GEX_HAB_no_lot" "S" "" "GEX_HAB_no_lot" ""))
    (if (=  (tblsearch "layer" "GEX_HAB_no_porte") nil)(command "-layer" "n" "GEX_HAB_no_porte" "CO" "U" "255,0,255" "GEX_HAB_no_porte" "TL" "continuous" "GEX_HAB_no_porte" "EP" "0.18" "GEX_HAB_no_porte" "S" "" "GEX_HAB_no_porte" ""))
    (if (=  (tblsearch "layer" "GEX_HAB_ouvrant_fenetre") nil)(command "-layer" "n" "GEX_HAB_ouvrant_fenetre" "CO" "U" "255,255,0" "GEX_HAB_ouvrant_fenetre" "TL" "cache2" "GEX_HAB_ouvrant_fenetre" "EP" "0.18" "GEX_HAB_ouvrant_fenetre" "S" "seulement pour les plans d'intérieur (pas de copro) - existence justifiée par calculs de surface s'arrêtant à la fenêtre mais pas aux ouvrants" "GEX_HAB_ouvrant_fenetre" ""))
    (if (=  (tblsearch "layer" "GEX_HAB_placard") nil)(command "-layer" "n" "GEX_HAB_placard" "CO" "U" "255,0,255" "GEX_HAB_placard" "TL" "continuous" "GEX_HAB_placard" "EP" "0.18" "GEX_HAB_placard" "S" "" "GEX_HAB_placard" ""))
    (if (=  (tblsearch "layer" "GEX_HAB_porte") nil)(command "-layer" "n" "GEX_HAB_porte" "CO" "U" "255,255,0" "GEX_HAB_porte" "TL" "continuous" "GEX_HAB_porte" "EP" "0.18" "GEX_HAB_porte" "S" "" "GEX_HAB_porte" ""))
    (if (=  (tblsearch "layer" "GEX_HAB_projection") nil)(command "-layer" "n" "GEX_HAB_projection" "CO" "U" "255,0,255" "GEX_HAB_projection" "TL" "continuous" "GEX_HAB_projection" "EP" "0.18" "GEX_HAB_projection" "S" "" "GEX_HAB_projection" ""))
    (if (=  (tblsearch "layer" "GEX_HAB_radiateur") nil)(command "-layer" "n" "GEX_HAB_radiateur" "CO" "U" "255,255,0" "GEX_HAB_radiateur" "TL" "continuous" "GEX_HAB_radiateur" "EP" "0.18" "GEX_HAB_radiateur" "S" "" "GEX_HAB_radiateur" ""))
    (if (=  (tblsearch "layer" "GEX_HAB_sanitaire") nil)(command "-layer" "n" "GEX_HAB_sanitaire" "CO" "U" "255,255,0" "GEX_HAB_sanitaire" "TL" "continuous" "GEX_HAB_sanitaire" "EP" "0.18" "GEX_HAB_sanitaire" "S" "" "GEX_HAB_sanitaire" ""))
    (if (=  (tblsearch "layer" "GEX_HAB_signal_sol") nil)(command "-layer" "n" "GEX_HAB_signal_sol" "CO" "U" "255,255,0" "GEX_HAB_signal_sol" "TL" "continuous" "GEX_HAB_signal_sol" "EP" "0.18" "GEX_HAB_signal_sol" "S" "" "GEX_HAB_signal_sol" ""))
    (if (=  (tblsearch "layer" "GEX_HAB_signal_verti") nil)(command "-layer" "n" "GEX_HAB_signal_verti" "CO" "U" "255,255,255" "GEX_HAB_signal_verti" "TL" "continuous" "GEX_HAB_signal_verti" "EP" "0.18" "GEX_HAB_signal_verti" "S" "" "GEX_HAB_signal_verti" ""))
    (if (=  (tblsearch "layer" "GEX_HAB_teinte") nil)(command "-layer" "n" "GEX_HAB_teinte" "CO" "U" "255,255,255" "GEX_HAB_teinte" "TL" "continuous" "GEX_HAB_teinte" "EP" "0.18" "GEX_HAB_teinte" "S" "" "GEX_HAB_teinte" ""))
    (if (=  (tblsearch "layer" "GEX_HAB_teinte_pc") nil)(command "-layer" "n" "GEX_HAB_teinte_pc" "CO" "U" "255,255,127" "GEX_HAB_teinte_pc" "TL" "continuous" "GEX_HAB_teinte_pc" "EP" "0.18" "GEX_HAB_teinte_pc" "S" "" "GEX_HAB_teinte_pc" ""))
    (if (=  (tblsearch "layer" "GEX_HAB_texte") nil)(command "-layer" "n" "GEX_HAB_texte" "CO" "U" "255,255,255" "GEX_HAB_texte" "TL" "continuous" "GEX_HAB_texte" "EP" "0.18" "GEX_HAB_texte" "S" "parties communes + texte topo" "GEX_HAB_texte" ""))
    (if (=  (tblsearch "layer" "GEX_HAB_trait_coupe") nil)(command "-layer" "n" "GEX_HAB_trait_coupe" "CO" "U" "252,255,0" "GEX_HAB_trait_coupe" "TL" "continuous" "GEX_HAB_trait_coupe" "EP" "0.18" "GEX_HAB_trait_coupe" "S" "" "GEX_HAB_trait_coupe" ""))
    (if (=  (tblsearch "layer" "GEX_MEP_carroyage") nil)(command "-layer" "n" "GEX_MEP_carroyage" "CO" "U" "255,255,255" "GEX_MEP_carroyage" "TL" "continuous" "GEX_MEP_carroyage" "EP" "0.18" "GEX_MEP_carroyage" "S" "" "GEX_MEP_carroyage" ""))
    (if (=  (tblsearch "layer" "GEX_MEP_ep") nil)(command "-layer" "n" "GEX_MEP_ep" "CO" "U" "255,255,255" "GEX_MEP_ep" "TL" "continuous" "GEX_MEP_ep" "EP" "0.18" "GEX_MEP_ep" "S" "Calques initiés par les gabarits de présentation" "GEX_MEP_ep" ""))
    (if (=  (tblsearch "layer" "GEX_MEP_fen_inv") nil)(command "-layer" "n" "GEX_MEP_fen_inv" "CO" "U" "255,0,0" "GEX_MEP_fen_inv" "TL" "continuous" "GEX_MEP_fen_inv" "EP" "0.30" "GEX_MEP_fen_inv" "S" "Calques initiés par les gabarits de présentation" "GEX_MEP_fen_inv" ""))
    (if (=  (tblsearch "layer" "GEX_REF") nil)(command "-layer" "n" "GEX_REF" "CO" "U" "255,0,0" "GEX_REF" "TL" "continuous" "GEX_REF" "EP" "0.30" "GEX_REF" "S" "en position ""jamais tracé""" "GEX_REF" ""))
    (if (=  (tblsearch "layer" "GEX_REF_station") nil)(command "-layer" "n" "GEX_REF_station" "CO" "U" "255,0,255" "GEX_REF_station" "TL" "continuous" "GEX_REF_station" "EP" "0.18" "GEX_REF_station" "S" "Supprimer à l'export client" "GEX_REF_station" ""))
    (if (=  (tblsearch "layer" "GEX_RES_AEP") nil)(command "-layer" "n" "GEX_RES_AEP" "CO" "U" "0,255,255" "GEX_RES_AEP" "TL" "continuous" "GEX_RES_AEP" "EP" "0.18" "GEX_RES_AEP" "S" "Les réseaux sont tracés par défaut en noir sur les plans topo - la gestion des couleurs est différente pour des plans de réseau (tracé en couleur)" "GEX_RES_AEP" ""))
    (if (=  (tblsearch "layer" "GEX_RES_assainissement") nil)(command "-layer" "n" "GEX_RES_assainissement" "CO" "U" "255,0,255" "GEX_RES_assainissement" "TL" "continuous" "GEX_RES_assainissement" "EP" "0.18" "GEX_RES_assainissement" "S" "" "GEX_RES_assainissement" ""))
    (if (=  (tblsearch "layer" "GEX_RES_eclairage") nil)(command "-layer" "n" "GEX_RES_eclairage" "CO" "U" "255,0,0" "GEX_RES_eclairage" "TL" "continuous" "GEX_RES_eclairage" "EP" "0.30" "GEX_RES_eclairage" "S" "Les réseaux sont tracés par défaut en noir sur les plans topo - la gestion des couleurs est différente pour des plans de réseau (tracé en couleur)" "GEX_RES_eclairage" ""))
    (if (=  (tblsearch "layer" "GEX_RES_elec") nil)(command "-layer" "n" "GEX_RES_elec" "CO" "U" "255,0,255" "GEX_RES_elec" "TL" "continuous" "GEX_RES_elec" "EP" "0.18" "GEX_RES_elec" "S" "Les réseaux sont tracés par défaut en noir sur les plans topo - la gestion des couleurs est différente pour des plans de réseau (tracé en couleur)" "GEX_RES_elec" ""))
    (if (=  (tblsearch "layer" "GEX_RES_ep_eu") nil)(command "-layer" "n" "GEX_RES_ep_eu" "CO" "U" "255,0,255" "GEX_RES_ep_eu" "TL" "continuous" "GEX_RES_ep_eu" "EP" "0.18" "GEX_RES_ep_eu" "S" "" "GEX_RES_ep_eu" ""))
    (if (=  (tblsearch "layer" "GEX_RES_gaz") nil)(command "-layer" "n" "GEX_RES_gaz" "CO" "U" "255,255,0" "GEX_RES_gaz" "TL" "continuous" "GEX_RES_gaz" "EP" "0.18" "GEX_RES_gaz" "S" "Les réseaux sont tracés par défaut en noir sur les plans topo - la gestion des couleurs est différente pour des plans de réseau (tracé en couleur)" "GEX_RES_gaz" ""))
    (if (=  (tblsearch "layer" "GEX_RES_tel") nil)(command "-layer" "n" "GEX_RES_tel" "CO" "U" "0,255,0" "GEX_RES_tel" "TL" "continuous" "GEX_RES_tel" "EP" "0.18" "GEX_RES_tel" "S" "Les réseaux sont tracés par défaut en noir sur les plans topo - la gestion des couleurs est différente pour des plans de réseau (tracé en couleur)" "GEX_RES_tel" ""))
    (if (=  (tblsearch "layer" "TopoAlt") nil)(command "-layer" "n" "TopoAlt" "CO" "U" "0,255,0" "TopoAlt" "TL" "continuous" "TopoAlt" "EP" "0.18" "TopoAlt" "S" "Calques créés par Covadis - détruits à l'export client - Hors Charte Graphiquecloison non porteuse" "TopoAlt" ""))
    (if (=  (tblsearch "layer" "TopoCod") nil)(command "-layer" "n" "TopoCod" "CO" "U" "255,0,0" "TopoCod" "TL" "continuous" "TopoCod" "EP" "0.30" "TopoCod" "S" "Calques créés par Covadis - détruits à l'export client - Hors Charte Graphique" "TopoCod" ""))
    (if (=  (tblsearch "layer" "TOPOJIS") nil)(command "-layer" "n" "TOPOJIS" "CO" "U" "255,255,255" "TOPOJIS" "TL" "continuous" "TOPOJIS" "EP" "0.18" "TOPOJIS" "S" "Calques créés par Covadis - détruits à l'export client - Hors Charte Graphique" "TOPOJIS" ""))
    (if (=  (tblsearch "layer" "TopoMat") nil)(command "-layer" "n" "TopoMat" "CO" "U" "0,255,255" "TopoMat" "TL" "continuous" "TopoMat" "EP" "0.18" "TopoMat" "S" "Calques créés par Covadis - détruits à l'export client - Hors Charte Graphique" "TopoMat" ""))


)
