(defun c:deplace_dim ( / distance_deplacement p0 p1 index_objet_a_deplacer jeu objet)
  ;(command "_.-purge" "_all" "*" "_yes")
  ;(command "_.ZOOM" "_extent")
  (initget 7)
  ;(alert )
  (setq distance_deplacement (getreal "\nInserer la distance adequate des objets: "))
  (setq p0 '(0.0 0.0))
  (setq p1 (list distance_deplacement 0.0))
  (setq index_objet_a_deplacer 0)
  (setq jeu (ssget))
  (repeat (sslength jeu)
	(setq objet (ssname jeu index_objet_a_deplacer))
  	(command "_.move" objet "" p0 p1)
  	(setq index_objet_a_deplacer (1+ index_objet_a_deplacer))
	(setq p1 (list (+ (car p1) distance_deplacement) 0.0))
   )
   (prin1)
)
