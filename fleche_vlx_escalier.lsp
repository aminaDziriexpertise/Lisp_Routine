;Dessin d'une flèche (fl[Escalier], flm[Marche], flp[Pointe], flf[Fin])
;Dessiner une flèche d'escalier
(defun c:fl (/ clay osmode_old p1 p2 p3 p4 p5 p6 p7 p8 p9 p10 p11 p12 la flType)
  ;(funINIT)
  ;(CI:Calq lay_escalier_rampe)
  (setq p1 1)
  (while (not (listp p1))
    (setvar "osmode" 2)
    (initget 128 "Echelle")
    (setq p1 (getpoint "\nPremier escalier bas ou [Echelle] : "))
    (cond
      ((null p1) (exit))
      ((listp p1))
      ((= p1 "Echelle") (c:echd))
    )
  )
  (setq p2 (getpoint p1 "\nPremier escalier haut : "))
  (initget "Terminé Palier Escalier")
  (setq opt1 (getkword "\nTerminé, Palier, Escalier : <Terminé> "))
  (if (= opt1 nil) (setq opt1 "Terminé"))
  (cond
    ((= opt1 "Terminé")
      (entmake (list
        '(0 . "LWPOLYLINE")'(100 . "AcDbEntity")'(100 . "AcDbPolyline") (cons 8 lay_escalier_rampe)'(90 . 4)'(40 . 0.0)'(41 . 0.0)
        (cons 10 (trans p2 1 0))(cons 41 (* 0.1 echd))
        (cons 10 (trans (polar p2 (angle p2 p1) (* 0.2 echd)) 1 0))'(41 . 0.0)
        (cons 10 (trans p1 1 0))
       ))
    )
    ((= opt1 "Palier")
      (setvar "osmode" 512)
      (setq p3 (getpoint "\nPalier coté escalier : "))
      (setvar "osmode" 1)
      (setq p4 (getpoint "\nPalier 1er point coté mur : "))
      (setvar "osmode" 1)
      (setq p5 (getpoint "\nPalier 2ème point coté mur : "))
      (setvar "osmode" 2)
      (setq p6 (getpoint "\nDeuxième escalier bas : "))
      (setq p7 (getpoint "\nDeuxième escalier haut : "))
      (entmake (list
        '(0 . "LWPOLYLINE")'(100 . "AcDbEntity")'(100 . "AcDbPolyline")(cons 8 lay_escalier_rampe)'(90 . 4)'(40 . 0.0)'(41 . 0.0)
        (cons 10 (trans p7 1 0))(cons 41 (* 0.1 echd))
        (cons 10 (trans (polar p7 (angle p7 p6) (* 0.2 echd)) 1 0))'(41 . 0.0)
        (cons 10 (trans (inters p6 p7 (ptMIL p3 p5) (polar (ptMIL p3 p5) (angle p4 p5) 0.5) nil) 1 0))
        (cons 10 (trans (inters p1 p2 (ptMIL p3 p5) (polar (ptMIL p3 p5) (angle p4 p5) 0.5) nil) 1 0))
        (cons 10 (trans p1 1 0))
       ))
    )
    ((= opt1 "Escalier")
      (setvar "osmode" 2)
      (setq p3 (getpoint "\nDeuxième escalier bas : "))
      (setq p4 (getpoint "\nDeuxième escalier haut : "))
      (initget "Terminé Escalier")
      (setq opt2 (getkword "\nTerminé, Escalier : <Terminé> "))
      (if (= opt2 nil) (setq opt2 "Terminé"))
      (cond
        ((= opt2 "Terminé")
          (entmake (list
            '(0 . "LWPOLYLINE")'(100 . "AcDbEntity")'(100 . "AcDbPolyline")(cons 8 lay_escalier_rampe)'(90 . 4)'(40 . 0.0)'(41 . 0.0)
            (cons 10 (trans p4 1 0))(cons 41 (* 0.1 echd))
            (cons 10 (trans (polar p4 (angle p4 p3) (* 0.2 echd)) 1 0))'(41 . 0.0)
            (cons 10 (trans (inters p1 p2 p3 p4 nil) 1 0))
            (cons 10 (trans p1 1 0))
           ))
        )
        ((= opt2 "Escalier")
            (setvar "osmode" 2)
            (setq p5 (getpoint "\nTroisième escalier bas  : "))
            (setq p6 (getpoint "\nTroisième escalier haut : "))
            (entmake (list
              '(0 . "LWPOLYLINE")'(100 . "AcDbEntity")'(100 . "AcDbPolyline")(cons 8 lay_escalier_rampe)'(90 . 4)'(40 . 0.0)'(41 . 0.0)
              (cons 10 (trans p6 1 0))(cons 41 (* 0.1 echd))
              (cons 10 (trans (polar p6 (angle p6 p5) (* 0.2 echd)) 1 0))'(41 . 0.0)
              (cons 10 (trans (inters p3 p4 p5 p6 nil) 1 0))
              (cons 10 (trans (inters p1 p2 p3 p4 nil) 1 0))
              (cons 10 (trans p1 1 0))
             ))
        )
      )
    )
  )
  ;(funQUIT)
  (princ)
)
;Dessiner unes flèche de marche
(defun c:flm (/ clay osmode_old p1 p2 p3 p4 p5 p6 p7 p8 p9 p10 p11 p12 la flType)
  ;(funINIT)
  ;(CI:Calq "GEX_BAT_sol")
  ;(setvar "clayer" "GEX_BAT_sol")
  (setq p1 1)
  (setvar "osmode" 1)
  (while (not (listp p1))
    (initget 128 "Echelle")
    (setq p1 (getpoint "\nPoint gauche de la marche ou [Echelle] : "))
  (cond
    ((null p1) (exit))
    ((listp p1))
    ((= p1 "Echelle") (c:echd))
    )
  )
  (setq p2 (getpoint p1 "\nPoint droit de la marche : "))
  (setq p3 (polar (ptMIL p1 p2) (+ (angle p1 p2) (/ pi 2)) (* 0.26 echd)))
  (setq p4 (polar (ptMIL p1 p2) (- (angle p1 p2) (/ pi 2)) (* 0.15 echd)))
  (entmake (list
    '(0 . "LWPOLYLINE")'(100 . "AcDbEntity")'(100 . "AcDbPolyline")(cons 8 lay_escalier_rampe)'(90 . 4)'(40 . 0.0)'(41 . 0.0)
    (cons 10 (trans p3 1 0))(cons 41 (* 0.08 echd))
    (cons 10 (trans (polar p3 (angle p3 p4) (* 0.17 echd)) 1 0))'(41 . 0.0)
    (cons 10 (trans p4 1 0))
   ))
 ; (funQUIT)
  (princ)
)
;Dessiner la pointe de la flèche
(defun c:flp (/ clay osmode_old p1 p2 la)
  ;(funINIT)
  ;(CI:Calq lay_escalier_rampe)
  (setvar "clayer" lay_escalier_rampe)
  (setq p1 1)
  (while (not (listp p1))
    (setvar "osmode" 1)
    (initget 128 "Echelle")
    (setq p1 (getpoint "\nSélectionnez le point d'insertion ou [Echelle] : "))
  (cond
  ((null p1) (exit))
    ((listp p1))
    ((= p1 "Echelle") (c:echd))
    )
  )
  (entmake (list
    '(0 . "LWPOLYLINE")'(100 . "AcDbEntity")'(100 . "AcDbPolyline")(cons 8 lay_escalier_rampe)'(90 . 4)'(40 . 0.0)'(41 . 0.0)
    (cons 10 (trans p1 1 0))(cons 41 (* 0.1 echd))
    (cons 10 (polar (trans p1 1 0) (* pi 0.5) (* 0.2 echd)))
  ))
  (setvar "osmode" 0)
  (vl-cmdf "._ROTATE" "_L" "" p1 "_R" (getUcsAng) pause)
  ;(funQUIT)
  (princ)
)

;;---------=={ Programme principal des routines Gexpetise }==---------;;
;;                                                                    ;;
;;--------------------------------------------------------------------;;
;;  Contributeurs : Nicolas Bullier                                   ;;
;;--------------------------------------------------------------------;;
;;  Version 1.0    -    01-01-2015                                    ;;
;;--------------------------------------------------------------------;;

;;On défini la date maximale d'utilisation - 31/12/2022 à 23h59m59s
(setq maxdate 20221231.235959)

;;;;;;;;;;;;;;;;;;;;;;;;;;;;;;;;;;;;;;;;;;;;;;;;;;;;;;;;;;;;;;;;;;;;;;;;
;Initialisation dessin
;;;;;;;;;;;;;;;;;;;;;;;;;;;;;;;;;;;;;;;;;;;;;;;;;;;;;;;;;;;;;;;;;;;;;;;;
(defun DRAWINIT (/ xrec)
  ;Contrôle l'affichage des attributs. (Normal)
  (setvar "ATTMODE" 1)
  ;Donne à l'angle de base la valeur 0 par rapport au SCU courant. (Nord - 300G)
  (setvar "ANGBASE" (/ pi 2))
  ;Définit la direction des angles positifs. (Sens horaire)
  (setvar "ANGDIR" 1)
  ;Détermine si la commande INSERER utilise une boîte de dialogue pour la saisie de la valeur d'attribut. (Inactif)
  (setvar "ATTDIA" 0)
  ;Définit les unités des angles. (Grades)
  (setvar "AUNITS" 2)
  ;Définit la précision d'affichage des unités angulaires et des coordonnées. (4 chiffres après la virgule)
  (setvar "AUPREC" 4)
  ;Détermine si les invites et les entrées sont reprises lors de la fonction de commande AutoLISP. (Inactif)
  (setvar "CMDECHO" 0)
  ;Controls whether AutoCAD runs in single- or multiple-document interface. (Actif)
  (setvar "SDI" 0)
  ;Contrôle l'associativité des objets cote et détermine si les cotes sont décomposées. (Cote groupée non attachée à l'objet)
  (setvar "DIMASSOC" 1)
  ;Contient le rayon de raccord courant. (0)
  (setvar "FILLETRAD" 0)
  ;Spécifie une valeur d'unités de dessin pour la mise à l'échelle automatique des blocs, images ou xréfs insérés ou associés à un dessin. (Mètre)
  (setvar "INSUNITS" 6)
  ;Définit la valeur des unités de contenu sources lorsque UnitésIns est définie sur 0. (Mètre)
  (setvar "INSUNITSDEFSOURCE" 6)
  ;Définit la valeur des unités de dessin cibles lorsque UnitésIns est définie sur 0. (Mètre)
  (setvar "INSUNITSDEFTARGET" 6)
  ;Détermine la quantité d'espace non utilisé toléré dans un fichier de dessin. (0)
  (setvar "ISAVEPERCENT" 0)
  ;Définit le facteur d'échelle du type de ligne global. (1)
  (setvar "LTSCALE" 1)
  ;Définit des unités linéaires. (Décimale)
  (setvar "LUNITS" 2)
  ;Détermine si un dessin commencé avec un brouillon utilise par défaut des unités anglo-saxonnes ou des unités métriques. (Système métrique)
  (setvar "MEASUREINIT" 1)
  ;Détermine si le dessin courant utilise des fichiers de type de ligne et des motifs de hachure métrique ou anglo-saxons. (Système métrique)
  (setvar "MEASUREMENT" 1)
  ;Gère la façon dont la commande MIROIR reflète le texte. (Conserve la direction du texte)
  (setvar "MIRRTEXT" 0)
  ;Contrôle si les cadres d'image s'affichent et sont tracés. (Les cadres d'image s'affichent mais ne sont pas tracés)
  (setvar "IMAGEFRAME" 2)
  ;Gère la suppression des zéros dans la valeur des unités principales. (Supprime les zéros de fin dans les cotes décimales)
  (setvar "DIMZIN" 0)
  ;Définit la façon dont sont générés les motifs de type de ligne autour des sommets d'une polyligne 2D.
  ;(Génère des polylignes qui commencent et se terminent par un tiret à chaque sommet.)
  (setvar "PLINEGEN" 0)
  ;Spécifie si les polylignes 2D optimisées sont utilisées. (Les polylignes des dessins de la Release 14 ou ultérieure d'AutoCAD sont
  ;converties à l'ouverture ; POLYLIGN crée des polylignes optimisées.)
  (setvar "PLINETYPE" 2)
  ;Gère la mise à l'échelle du type de ligne des objets affichés dans les fenêtres de l'espace papier.
  ;(Aucune mise à l'échelle particulière du type de ligne. La longueur des tirets dépend des unités de
  ;dessin de l'espace (objet ou papier) dans lequel les objets sont créés. Mise à l'échelle effectuée par le facteur ECHLTP général.)
  (setvar "PSLTSCALE" 0)
  ;Définit le type d'ellipse créé par la commande ELLIPSE. (Crée la représentation d'une ellipse sous la forme d'une polyligne)
  (setvar "PELLIPSE" 1)
  ;Gère le fenêtrage automatique lors de l'affichage de l'invite Choix des objets. (Dessine automatiquement une fenêtre de sélection
  ;(pour une fenêtre ou une fenêtre de capture) à l'invite Sélectionner les objets)
  (setvar "PICKAUTO" 1)
  ;Gère la régénération automatique du dessin. (Active la commande REGNAUTO)
  (setvar "REGENMODE" 1)
  ;Gère le remplissage des polices TrueType pendant le traçage. (Affiche le texte sous forme d'images pleines)
  (setvar "TEXTFILL" 1)
  ;Gère la visibilité et la position de l'icône SCU. (On; the icon is displayed in the lower-left corner of the current viewport or layout)
  (setvar "UCSICON" 1)
  ;Génère une vue en plan chaque fois que vous passez d'un SCU à un autre. (Le SCU n'a pas d'incidence sur la vue.)
  (setvar "UCSFOLLOW" 0)
  ;Détermine l'ampleur de l'agrandissement lorsque la roulette de la souris bouge dans un sens ou dans un autre. (60)
  (setvar "ZOOMFACTOR" 60)
  ;Détermine si les contraintes géométriques sont déduites lors du dessin et de la modification de la géométrie. (Les contraintes géométriques ne sont pas déduites)
 ; (setvar "CONSTRAINTINFER" 0)
  ;Supprime l'affichage de l'invite L'objet sélectionné n'est pas une polyligne dans PEDIT. (l'invite est supprimée)
  (setvar "PEDITACCEPT" 1)
  ;Epaisseur des traits par défaut à 0
  (setvar "lwdefault" 0)
  ;(command "blipmode" "0")
  ;(command "delobj" "0")
  ;(command "dimaso" "ac")
  ;(command "osmode" "33")
  (princ)
)
;;;;;;;;;;;;;;;;;;;;;;;;;;;;;;;;;;;;;;;;;;;;;;;;;;;;;;;;;;;;;;;;;;;;;;;;
;Référence calques
;;;;;;;;;;;;;;;;;;;;;;;;;;;;;;;;;;;;;;;;;;;;;;;;;;;;;;;;;;;;;;;;;;;;;;;;
(setq lay_allege "GEX_BAT_allege")
(setq lay_ouv_porte "GEX_MEP_ouvrant_porte")
(setq lay_lint_mur "GEX_BAT_linteau_mur")
(setq lay_lint_cloison "GEX_BAT_linteau_cloison")
(setq lay_mur "GEX_BAT_mur")
(setq lay_cloison "GEX_BAT_cloison")
(setq lay_brut_report "brut_report")
(setq lay_tremie "GEX_MEP_mur_pochage")
(setq lay_COT_Z "GEX_MEP_txt_cot_alti")
(setq lay_COT_hauteur "GEX_MEP_txt_cot_alti")
(setq lay_Z_allege_linteau "GEX_MEP_txt_cot_alti")
(setq lay_radiateur "GEX_RES_bat_radiateur")
(setq lay_placard "GEX_BAT_placard")
(setq lay_h-180 "GEX_MEP_h-180")
(setq lay_mur_poch "GEX_MEP_mur_pochage")
(setq lay_mur_hach "GEX_MEP_mur_hachurage")
(setq lay_menuiserie "GEX_BAT_menuis_ext")
(setq lay_modenature "GEX_BAT_façade")
(setq lay_ouvrant_fenetre "GEX_MEP_ouvrant_fenetre")
(setq lay_ouvrant_placard "GEX_MEP_ouvrant_placard")
(setq lay_escalier_rampe "GEX_BAT_escalier_rampe")
(setq lay_TXT_divers "GEX_MEP_txt_divers")
(setq lay_cesure "GEX_MEP_cesure")
(setq lay_cot_plani "GEX_MEP_txt_cot_plani")
(setq lay_san "GEX_EQU_sanitaire")
;;;;;;;;;;;;;;;;;;;;;;;;;;;;;;;;;;;;;;;;;;;;;;;;;;;;;;;;;;;;;;;;;;;;;;;;
;Code SNIPPET
;;;;;;;;;;;;;;;;;;;;;;;;;;;;;;;;;;;;;;;;;;;;;;;;;;;;;;;;;;;;;;;;;;;;;;;;
;Donne le milieu entre "pt1" et "pt2"
(defun ptMIL (pt1 pt2)
  (mapcar (function (lambda (x) (/ x 2.0)))
    (mapcar '+ pt1 pt2)
  )
)
;Renvoie la tangente d'un angle "a"
(defun tan (a) (/ (sin a) (cos a)))
;Calcul le distance d'une droite à un point perpendiculairement
(defun getLenPerp (pt1 pt2 pt3)
(setq pt4 (polar pt3 (+ (angle pt1 pt2) (/ pi 2)) 0.5))
(setq pt5 (inters pt1 pt2 pt3 pt4 nil))
(distance pt5 pt3)
)
;; Clockwise-p  -  gile
;; Returns T if p1,p2,p3 are clockwise oriented
(defun clockwise-p ( p1 p2 p3 )
    (< (sin (- (angle p1 p3) (angle p1 p2))) -1e-14)
)
;Transforme un angle radian -> grade
(defun rtog (ang)
(- (/ (* ang -200) pi) 100)
)
;Renvoie l'angle de référence (Nord) selon le SCU courant.
(defun getUcsAng ()
(rtog (angle (trans '(0 1 0) 0 1 ) (trans '(0 0 0) 0 1 )))
)
;Initialise la fonction
(defun funINIT()
  (GX:SecurityCheck)
  (setq derniere_erreur *error* *error* getErr)
  (setq clay (getvar "clayer"))
  (setq osmode_old (getvar "osmode"))
  (vla-startundomark *thisdrawing*)
)
(defun getErr (msg)
  (setq *error* derniere_erreur)
  (funQUIT)
  (princ)
)
;Clos la fonction
(defun funQUIT()
  (vla-endundomark *thisdrawing*)
  (setvar "clayer" clay)
  (setvar "osmode" osmode_old)
  (princ)
)

;;;;;;;;;;;;;;;;;;;;;;;;;;;;;;;;;;;;;;;;;;;;;;;;;;;;;;;;;;;;;;;;;;;;;;;;
;Donne l'echelle du dessin (echd)
;;;;;;;;;;;;;;;;;;;;;;;;;;;;;;;;;;;;;;;;;;;;;;;;;;;;;;;;;;;;;;;;;;;;;;;;
(defun c:echd (/ echd1 fact)
  (setq echd1 (getreal (strcat "\nEchelle du dessin (1/XXX) - Courante = 1/" (rtos (* echd 100) 2 0) " : <100> ")))
  (if (= echd1 nil) (setq echd1 100))
  (setvar "userr4" (/ echd1 100))
  (echdINIT)
  (princ))
(defun echdINIT ()
  (setq echd (getvar "userr4"))
  (if (= echd 0) (setq echd 1))
  (princ))
;;;;;;;;;;;;;;;;;;;;;;;;;;;;;;;;;;;;;;;;;;;;;;;;;;;;;;;;;;;;;;;;;;;;;;;;;
;Initialisation du dessin
;;;;;;;;;;;;;;;;;;;;;;;;;;;;;;;;;;;;;;;;;;;;;;;;;;;;;;;;;;;;;;;;;;;;;;;;;
;(echdinit)
;(drawinit)
(vl-load-com)
(setq *thisdrawing* (vla-get-activedocument (vlax-get-acad-object)))
(Prompt "\nRoutines Gexpertise chargée !\n")
(princ)
